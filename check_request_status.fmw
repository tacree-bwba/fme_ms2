FME workspace check_request_status.fmw

Parameters:
- request_id = 08cd555a-6396-4c61-918a-5df4197266c9   # Enter the request ID
- DEFAULT_API_KEY = a088167b-f628-4d44-81ad-4c6348faa72d   # Enter Default API Key
- SourceDataset_POSTGRES = postgisdb   # Connection
- BASE_URL = https://odot.ms2soft.com/TDMS/Services/BackupAPI   # Enter Base URL
- DestDataset_POSTGRES = postgisdb   # Connection

Readers:
- POSTGRES_1: POSTGRES from $(SourceDataset_POSTGRES)

Writers:
- POSTGRES_2: POSTGRES to $(DestDataset_POSTGRES)

ms2_fme_process (reader POSTGRES_1)
    attributes: request_id varchar(40), api_key varchar(80), datasets varchar(200), start_date timestamp, end_date timestamp, row_limit int8, submit_request_url varchar(1000), status varchar(40), download_url varchar(1000)
    -> AttributeManager
AttributeManager
    ATTR_TABLE:
      SET_TO status_url = $(BASE_URL)/GetStatus?key=$(DEFAULT_API_KEY)&requestId=$(request_id)
      SET_TO request_download_url = $(BASE_URL)/GetDownloadUrl?key=$(DEFAULT_API_KEY)&requestId=$(request_id)
    -> GetStatusHTTPCaller
GetStatusHTTPCaller: HTTPCaller
    CONNECTION_TIMEOUT_LENGTH = 60
    ERROR_ATTR = _status_error
    FOLLOW_REDIRECTS = FOLLOW_WITH_GET
    HTTP_METHOD = GET
    REDIRECT_AUTH = ORIGINAL_DOMAIN_ONLY
    SAVE_FILE = Attribute
    STATUS_CODE_ATTR = _status_http_status_code
    TARGET_ATTR = _status_response
    TARGET_ATTR_ENCODING = utf-8
    TARGET_URL = @Value(status_url)
    TRANSFER_TIMEOUT_LENGTH = 90
    USE_COOKIES = No
    VERIFY_SSL_CERTIFICATES = Yes
    -> downLoadUrlHTTPCaller
    <REJECTED> -> LogFailedGetStatus
downLoadUrlHTTPCaller: HTTPCaller
    CONNECTION_TIMEOUT_LENGTH = 60
    ERROR_ATTR = _download_error
    FOLLOW_REDIRECTS = FOLLOW_WITH_GET
    HTTP_METHOD = GET
    REDIRECT_AUTH = ORIGINAL_DOMAIN_ONLY
    SAVE_FILE = Attribute
    STATUS_CODE_ATTR = _download_http_status_code
    TARGET_ATTR = _download_response
    TARGET_ATTR_ENCODING = utf-8
    TARGET_URL = @Value(request_download_url)
    TRANSFER_TIMEOUT_LENGTH = 90
    USE_COOKIES = No
    VERIFY_SSL_CERTIFICATES = Yes
    -> AttributeManager_2
    <REJECTED> -> LogFailedGetDownloadUrl
AttributeManager_2
    ATTR_TABLE:
      SET_TO status = ready
      SET_TO download_url = @Value(_download_response)
    -> VerifyStatus
VerifyStatus: TestFilter
    DEFAULT_VALUE = failed
    TEST_LIST = "BOOL_OP,OR,COMPOSITE_TEST,""""""1"""""",TEST_CLAUSE,TEST request_download_url ATTRIBUTE_HAS_A_VALUE """,ready
    ready -> output
    ready -> ms2_fme_process (writer POSTGRES_2)
    failed -> LogMissingDownloadUrl
output: Inspector
ms2_fme_process (writer POSTGRES_2)
    attributes: request_id varchar(40), status varchar(40), download_url varchar(1000)
LogMissingDownloadUrl: Logger
    LOG_FEATURE = LOG_ONLY
    MAXCOORDS = 20
    MAXFEATS = 20
    MESSAGE = Missing expected download url for request id: @Value(request_id) failed for url: @Value(request_download_url)
    SEVERITY = ERROR
LogFailedGetDownloadUrl: Logger
    LOG_FEATURE = LOG_ONLY
    MAXCOORDS = 20
    MAXFEATS = 20
    MESSAGE = GetStatus for request id: @Value(request_id) failed for url: @Value(request_download_url) with the error: @Value(_download_error)
    SEVERITY = ERROR
LogFailedGetStatus: Logger
    LOG_FEATURE = LOG_ONLY
    MAXCOORDS = 20
    MAXFEATS = 20
    MESSAGE = GetStatus for request id: @Value(request_id) failed for url: @Value(status_url) with the error: @Value(_status_error)
    SEVERITY = ERROR
