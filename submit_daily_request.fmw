FME workspace submit_daily_request.fmw

Parameters:
- DATE = 20200310   # START_DATE "{}" Enter Start Date
- END_DATE = 20200311   # "{}" Enter End Date
- MS2_BASE_URL = https://odot.ms2soft.com/TDMS/Services/BackupAPI   # Provide Base Url for MS2 Backup API
- API_KEY = a088167b-f628-4d44-81ad-4c6348faa72d   # Enter API Key
- Datasets = BinHeader BinCount Count Location   # Select Datasets to Load
- DestDataset_POSTGRES = postgisdb   # Connection
- FME_SHAREDRESOURCE_DATA = /Users/tacree/projects/fme/ms2/data   # FME Server Data Directory

Writers:
- POSTGRES_1: POSTGRES to $(DestDataset_POSTGRES)

Creator
    GEOMTYPE = Geometry Object
    NUM = 1
    CREATED -> UUIDGenerator
UUIDGenerator
    UUID_ATTR = request_id
    -> DateTimeStamper
DateTimeStamper
    DATETIME_ATTR = _today
    STAMP_TYPE = date
    TIMEZONE = local
    -> DateTimeCalculator
DateTimeCalculator
    MODE = DATETIMECALC_1_ADD_INTERVAL
    OPERATION_PARAMETERS = START_DATETIME]@Value(_today)]OPERATOR]SUBTRACT]YEARS]0]MONTHS]0]DAYS]1]HOURS]0]MINUTES]0]SECONDS]0]RESULT_DATETIME]_yesterday]FME_CONTROLLER_QUERY_FILE]transformers/dependencies/datetimecalculator/DATETIMECALC_1_ADD_INTERVAL.fme
    -> AttributeManager
AttributeManager
    ATTR_TABLE:
      SET_TO _startDateInput = $(START_DATE)
      SET_TO _endDateInput = $(END_DATE)
      SET_TO datasets = @ReplaceString($(Datasets)," ",",")
      SET_TO startDate = FME_CONDITIONAL:DEFAULT_VALUE'@Value(_yesterday)'BOOL_OP;OR;COMPOSITE_TEST;1;TEST _startDateInput ATTRIBUTE_HAS_A_VALUE _FME_BLANK_STRING_'@Value(_startDateInput)'FME_NUM_CONDITIONS2___
      SET_TO endDate = FME_CONDITIONAL:DEFAULT_VALUE'@Value(_today)'BOOL_OP;OR;COMPOSITE_TEST;1;TEST _endDateInput ATTRIBUTE_HAS_A_VALUE _FME_BLANK_STRING_'@Value(_endDateInput)'FME_NUM_CONDITIONS2___
      SET_TO startDateFmt = @DateTimeFormat(@Value(startDate), "%m/%d/%Y 12:00:00 AM")
      SET_TO endDateFmt = @DateTimeFormat(@Value(endDate), "%m/%d/%Y 12:00:00 AM")
      SET_TO rowLimit = 100
      SET_TO submitRequestUrlBroken = $(MS2_BASE_URL)/SubmitRequest?requestId=@Value(request_id)&StartDate=@Value(startDateFmt)&EndDate=@Value(endDateFmt)&rowLimit=100&includeQueries=@Value(datasets)
      SET_TO submitRequestUrl = $(MS2_BASE_URL)/SubmitRequest?key=$(API_KEY)&requestId=@Value(request_id)&StartDate=@Value(startDateFmt)&EndDate=@Value(endDateFmt)&includeQueries=@Value(datasets)
    -> HTTPCallerSubmitBackupRequest
HTTPCallerSubmitBackupRequest
    CONNECTION_TIMEOUT_LENGTH = 60
    ERROR_ATTR = _error
    FOLLOW_REDIRECTS = Yes
    HTTP_METHOD = GET
    SAVE_FILE = Attribute
    STATUS_CODE_ATTR = _http_status_code
    TARGET_ATTR = _response
    TARGET_ATTR_ENCODING = auto-detect
    TARGET_URL = @Value(submitRequestUrl)
    TRANSFER_TIMEOUT_LENGTH = 90
    USE_COOKIES = No
    VERIFY_SSL_CERTIFICATES = No
    -> output
    -> AttributeManager_2
    <REJECTED> -> FailedSubmitTerminator
output: Inspector [off]
AttributeManager_2
    ATTR_TABLE:
      SET_TO api_key = $(API_KEY)
      RENAME_SET_VALUE startDate > start_date
      RENAME_SET_VALUE endDate > end_date
      RENAME_SET_VALUE rowLimit > row_limit
      RENAME_SET_VALUE submitRequestUrl > submit_request_url
      SET_TO status = submitted
      SET_TO download_url = FME_NULL_VALUE
      REMOVE _http_status_code
      REMOVE _creation_instance
      REMOVE _today
      REMOVE _yesterday
      REMOVE _startDateInput
      REMOVE _endDateInput
      REMOVE startDateFmt
      REMOVE endDateFmt
      REMOVE submitRequestUrlBroken
      REMOVE _response
    -> ms2_fme_process (writer POSTGRES_1)
ms2_fme_process (writer POSTGRES_1)
    attributes: request_id varchar(40), api_key varchar(80), datasets varchar(200), start_date timestamp, end_date timestamp, row_limit int8, submit_request_url varchar(1000), status varchar(40), download_url varchar(1000)
FailedSubmitTerminator: Terminator
    MESSAGE = Submit request failed with a status of: @Value(_http_status_code) and an error message of: @Value(_error)
