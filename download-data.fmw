FME workspace download-data.fmw

Parameters:
- SourceDataset_POSTGRES = postgisdb   # Connection
- FME_SHAREDRESOURCE_DATA = $(FME_MF_DIR)data   # FME Server Data Directory

Readers:
- POSTGRES_1: POSTGRES from $(SourceDataset_POSTGRES)

ms2_fme_process (reader POSTGRES_1)
    attributes: request_id varchar(40), datasets varchar(200), start_date timestamp, end_date timestamp, row_limit int8, submit_request_url varchar(1000), status varchar(40), download_url varchar(1000), process_dt timestamp
    -> AttributeManager
AttributeManager
    ATTR_TABLE = SET_TO download_file = $(FME_SHAREDRESOURCE_DATA)/ms2/@Value(request_id).zip
    -> HTTPCaller
HTTPCaller
    CONNECTION_TIMEOUT_LENGTH = 60
    ERROR_ATTR = _error
    FILE_PATH_ATTR = _response_file_path
    FOLLOW_REDIRECTS = Yes
    HTTP_METHOD = GET
    OUTPUT_FILENAME = @Value(download_file)
    SAVE_FILE = File
    SAVE_MULTI = No
    STATUS_CODE_ATTR = _http_status_code
    TARGET_URL = https://s3.amazonaws.com/MS2-ReportOutput/BackupApi/25-2020326-96478c21-3331-4d8a-9c4c-64b465a3eae3.zip?AWSAccessKeyId=AKIAIM57LTEYVUS345GA&Expires=1585855719&Signature=stXekPNyW2Ml8rmA98umnEYC36Y%3D
    TRANSFER_TIMEOUT_LENGTH = 90
    USE_COOKIES = No
    VERIFY_SSL_CERTIFICATES = Yes
    -> ZipExtractor
ZipExtractor
    PRESERVE = No
    RECURSIVE = No
    REPLACE = No
    ROOT_FOLDER = $(FME_SHAREDRESOURCE_DATA)/ms2
    ZIP_PATH = @Value(_response_file_path)
    File -> TestFilter
TestFilter
    DEFAULT_VALUE = <UNFILTERED>
    TEST_LIST = "BOOL_OP,OR,COMPOSITE_TEST,""""""1"""""",TEST_CLAUSE,CASE_INSENSITIVE_TEST @Value(path_windows) CONTAINS COUNT.CSV",COUNT
    COUNT -> FeatureReader [INITIATOR]
FeatureReader
    ATTRS_TO_EXPOSE = AADT TOTAL
    ATTR_ACCUM_MODE = Only Use Result
    COMBINE_GEOM = Use Result
    CSV2_CASE_SENSITIVE_FIELD_NAMES = Yes
    CSV2_DATA_START_LINE = 2
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = YES
    DATASET = @Value(path_windows)
    FORMAT = CSV2
    INTERACT = <No Spatial Filter>
    OUTPUT_FEATURES_DISPLAY = Schema and Data Features
    <SCHEMA> -> countSchema
    <OTHER> -> AttributeExposer
countSchema: Inspector
AttributeExposer
    ATTR_LIST = AADT,AADT_FACTOR_OR,ABNORMAL,AGENCY_ID,BY_AXLE,condition,COUNT_STATUS_ID,COUNT_STATUS_UPDATED_DATE,COUNT_TECHNICIAN,DIR,END_DATE,END_TIME,FILENAME,FO,H01,H01_1,H01_2,H01_3,H01_4,H02,H02_1,H02_2,H02_3,H02_4,H03,H03_1,H03_2,H03_3,H03_4,H04,H04_1,H04_2,H04_3,H04_4,H05,H05_1,H05_2,H05_3,H05_4,H06,H06_1,H06_2,H06_3,H06_4,H07,H07_1,H07_2,H07_3,H07_4,H08,H08_1,H08_2,H08_3,H08_4,H09,H09_1,H09_2,H09_3,H09_4,H10,H10_1,H10_2,H10_3,H10_4,H11,H11_1,H11_2,H11_3,H11_4,H12,H12_1,H12_2,H12_3,H12_4,H13,H13_1,H13_2,H13_3,H13_4,H14,H14_1,H14_2,H14_3,H14_4,H15,H15_1,H15_2,H15_3,H15_4,H16,H16_1,H16_2,H16_3,H16_4,H17,H17_1,H17_2,H17_3,H17_4,H18,H18_1,H18_2,H18_3,H18_4,H19,H19_1,H19_2,H19_3,H19_4,H20,H20_1,H20_2,H20_3,H20_4,H21,H21_1,H21_2,H21_3,H21_4,H22,H22_1,H22_2,H22_3,H22_4,H23,H23_1,H23_2,H23_3,H23_4,H24,H24_1,H24_2,H24_3,H24_4,ID,IMPORT_TIMESTAMP,IMPORT_TYPE,INTERVAL,LATITUDE,LOCAL_ID,LOCATION_DESC,LONGITUDE,OWNER_ID,SENSOR_TYPE_ID,SOURCE,SPEED_LIMIT,ST_DATE,ST_TIME,STATION,TOTAL,weather
    -> DateTimeConverter
DateTimeConverter
    DATETIME_ATTR = COUNT_STATUS_UPDATED_DATE END_DATE END_TIME IMPORT_TIMESTAMP ST_DATE ST_TIME
    IN_FORMAT = %Y%m%d%H%M%S
    OUT_FORMAT = FME
    PASSTHROUGH = YES
    REPAIR_INPUT = YES
    TEST_INPUT = 20200326052851253
    -> AttributeManager_2
AttributeManager_2
    NUM_PRIOR_FEATURES = 0
    NUM_SUBSEQUENT_FEATURES = 0
    -> CountOutput
CountOutput: Inspector

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- ZIP_PATH =   # Source Zip File
- ROOT_FOLDER =   # Destination Root Folder
- REPLACE = No   # Replace Existing Destination Subfolder
- RECURSIVE = No   # Unzip Nested Zip Files Recursively
- PRESERVE = No   # Preserve Nested Zip Files
- EXT_S =   # Allowable Source Zip File Extension(s)
- EXT_N =   # Allowable Nested Zip File Extension(s)

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.zip_path __unzipper.ext_s __unzipper.replace __unzipper.recursive __unzipper.root_folder __unzipper.preserve
    NEW_ATTRIBUTES = path_unix path_windows path_depth __unzipper.flag _error_message
    PYTHONSOURCE:
      # 2016-01-21, Takashi Iijima, Original Implementation
      # 2016-01-23, Takashi Iijima, Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-25, Takashi Iijima, Updated to trim leading and trailing whitespaces of specified path strings.
      # 2018-06-14, Takashi Iijima, Added Allowable Source/Nested Zip File Extention(s) parameter.
      # 2019-01-13, Takashi Iijima, Fixed the destination folder name derived from zip filename which has non-4-letters suffix (e.g. ".xlsx").
      # 2020-01-13, Takashi Iijima, Changed Default Python Interpreter to 3.6+, saved with FME 2017.1.2.1

      import fmeobjects, zipfile, os

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip']) # Filename extensions source (root) zip files
              self.zipExtN = set(['.zip']) # Filename extensions for archived (descendant) zip files

          # Returns the number of characters of the zip file extension
          # if the path points a valid zip file, 0 otherwise.
          def zipExtLen(self, path, zipExt):
              _, ext = os.path.splitext(path)
              return len(ext) if (ext.lower() in zipExt and zipfile.is_zipfile(path)) else 0

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) \
                  or self.zipExtLen(zipPath, self.zipExtS) == 0 \
                  or not isRootValid:
                  msg = 'Specified zip file or destination root folder is invalid.'
                  self.logger.logMessageString(msg, fmeobjects.FME_ERROR)
                  feature.setAttribute('_error_message', msg)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              rootName, _ = os.path.splitext(zipName)
              destFolder = os.path.join(os.path.abspath(rootFolder) if rootFolder else zipFolder, rootName)

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath, destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  msg = 'Unexpected error: %s' % ex
                  self.logger.logMessageString(msg, fmeobjects.FME_ERROR)
                  feature.setAttribute('_error_message', msg)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive:
                      n = self.zipExtLen(path, self.zipExtN)
                      if n != 0:
                          if self.preserve:
                              self.pathInfos.append((path, self.kFlagFile, depth))
                              self.extract(path, os.path.join(dirPath, fname[:-n]), depth)
                          else:
                              self.extract(path, os.path.join(dirPath, fname[:-n]), depth)
                              os.remove(path)
                      else:
                          self.pathInfos.append((path, self.kFlagFile, depth))
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> <Rejected> (output)
File (output)
Directory (output)
<Rejected> (output)
